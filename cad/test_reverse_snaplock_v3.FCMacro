"""FreeCAD checks and mesh comparison for reverse_snaplock_v3.FCStd.

Run after cad/reverse_snaplock_v3.FCMacro. Source remains read only.
Reports surface error; this is a reconstruction study, not print-fit certification.
"""
from pathlib import Path
from zipfile import ZipFile
import json
import math
import xml.etree.ElementTree as ET
import FreeCAD as App
import Part
import Mesh

ROOT = Path(__file__).resolve().parents[1]
SOURCE = Path('/home/xynogen/Downloads/150x50x25.3mf')


def main():
    doc = App.openDocument(str(ROOT / 'reverse_snaplock_v3.FCStd'))
    try:
        bodies = [doc.getObject(n) for n in ('Latch', 'BaseCoupon', 'TopCoupon')]
        for obj in doc.Objects:
            if obj.TypeId == 'Sketcher::SketchObject':
                assert obj.FullyConstrained and obj.solve() == 0, obj.Name
                assert all(c.Type != 'Block' for c in obj.Constraints), obj.Name
        for obj in bodies:
            assert obj.Shape.isValid() and len(obj.Shape.Solids) == 1, obj.Name
        for a, b in ((bodies[0], bodies[1]), (bodies[0], bodies[2]), (bodies[1], bodies[2])):
            volume = a.Shape.common(b.Shape).Volume
            assert volume < 0.001, f'{a.Name}/{b.Name}: collision {volume:g} mm3'

        # Captive upper snap: small tip lead-in and square socket mouths retain the seating land.
        assert math.isclose(doc.TopCatch.Length.Value, 15.3, abs_tol=1e-6)
        assert math.isclose(doc.HookLeadIn.Size.Value, .35, abs_tol=1e-6)
        assert doc.getObject('ReceiverLeadIn') is None
        assert len(doc.HookLeadIn.Base[1]) == 2, 'Both snap tips need a lead-in'
        assert doc.HookLeadIn.Shape.Volume < doc.RightHookTip.Shape.Volume
        assert math.isclose(doc.LeftTipReceiverProfile.Geometry[0].Radius, 2.65, abs_tol=1e-6)
        assert math.isclose(doc.RightHookTip.Length.Value, 2.2, abs_tol=1e-6)
        assert 2.2-doc.HookLeadIn.Size.Value > 1, 'Keep a cylindrical seating land'
        assert math.isclose(doc.Parameters.TopTipClearance.Value, .15, abs_tol=1e-6)
        assert math.isclose((16-doc.TopCatch.Length.Value)/2, .35, abs_tol=1e-6)
        print('PASS: 0.15 mm radial/0.35 mm side clearance and square socket mouths; retention needs physical testing.')

        # Normal wall thickness between the circular socket and its 45-degree outer roof.
        roof = doc.TopCatchProfile.Geometry[5]
        normal = App.Vector(-(roof.EndPoint-roof.StartPoint).y, (roof.EndPoint-roof.StartPoint).x, 0)
        normal.normalize()
        roof_wall = abs((App.Vector(2.5, 37.5, 0)-roof.StartPoint).dot(normal))-2.65
        assert roof_wall > 1.5, f'Thin socket roof: {roof_wall:g} mm'
        assert math.isclose(doc.Parameters.SocketRoofRise.Value, 2, abs_tol=1e-6)
        initial_volume = bodies[2].Shape.Volume
        roof_cell = doc.Parameters.getCellFromAlias('SocketRoofRise')
        doc.Parameters.set(roof_cell, '2.2 mm')
        doc.recompute()
        assert bodies[2].Shape.Volume > initial_volume+.1, 'SocketRoofRise does not drive roof'
        assert bodies[2].Shape.isValid() and len(bodies[2].Shape.Solids) == 1
        for obj in doc.Objects:
            assert 'Invalid' not in obj.State, (obj.Name, obj.State)
        doc.Parameters.set(roof_cell, '2 mm')
        doc.recompute()
        print(f'PASS: socket-to-sloping-roof wall {roof_wall:.3f} mm; pin bore and block width unchanged.')

        # Entry ramps narrow the nose without opening a channel into the seated sockets.
        for side in (-1, 1):
            assert not bodies[2].Shape.isInside(App.Vector(side*7, -1, 35), 1e-6, True), 'Entry ramp missing'
            assert bodies[2].Shape.isInside(App.Vector(side*5.5, -1, 35), 1e-6, True), 'Entry nose removed'
            assert bodies[2].Shape.isInside(App.Vector(side*7.5, -.15, 37.5), 1e-6, True), 'Socket retaining lip removed'
        initial_volume = bodies[2].Shape.Volume
        entry_cell = doc.Parameters.getCellFromAlias('TopEntryWidth')
        doc.Parameters.set(entry_cell, '11.8 mm')
        doc.recompute()
        assert bodies[2].Shape.Volume > initial_volume+.01, 'TopEntryWidth does not drive ramps'
        for obj in doc.Objects:
            assert 'Invalid' not in obj.State, (obj.Name, obj.State)
        assert bodies[2].Shape.isValid() and len(bodies[2].Shape.Solids) == 1
        doc.Parameters.set(entry_cell, '11.6 mm')
        doc.recompute()
        print('PASS: tapered entry nose, adjustable width, and intact socket retaining lips; insertion force unverified.')

        assert doc.getObject('LeftEntryCorner') is not None and doc.getObject('RightEntryCorner') is not None
        assert math.isclose(doc.Parameters.EntryEdgeChamfer.Value, .1, abs_tol=1e-6)
        assert bodies[2].Shape.Volume < doc.RightEntryRamp.Shape.Volume
        initial_volume = bodies[2].Shape.Volume
        chamfer_cell = doc.Parameters.getCellFromAlias('EntryEdgeChamfer')
        doc.Parameters.set(chamfer_cell, '0.08 mm')
        doc.recompute()
        assert bodies[2].Shape.Volume > initial_volume+1e-4, 'EntryEdgeChamfer does not drive geometry'
        assert bodies[2].Shape.isValid() and len(bodies[2].Shape.Solids) == 1
        for obj in doc.Objects:
            assert 'Invalid' not in obj.State, (obj.Name, obj.State)
        doc.Parameters.set(chamfer_cell, '0.1 mm')
        doc.recompute()
        print('PASS: 0.1 mm chamfer on both ramp-to-side corners; seating dimensions unchanged.')


        for side in (-1, 1):
            assert not bodies[0].Shape.isInside(App.Vector(side*11.75, -3, 10), 1e-6, True), 'Lower flex gap missing'
            assert bodies[0].Shape.isInside(App.Vector(side*12.25, -3, 10), 1e-6, True), 'Lower pivot arm missing'
        for side in (-1, 1):
            # Above the relief the plate must be continuous instead of notched.
            assert bodies[0].Shape.isInside(App.Vector(side*11.75, -3, 21.6), 1e-6, True), 'Notch remains above relief'
            assert not bodies[0].Shape.isInside(App.Vector(side*14, -1.8, 20.25), 1e-6, True), 'Triangular remnant in side relief'
            assert bodies[0].Shape.isInside(App.Vector(side*14, -1.8, 19.9), 1e-6, True), 'Lower arm removed'
        for label in ('Left', 'Right'):
            profile = doc.getObject(label+'FlexureReliefProfile')
            for arc in profile.Geometry[:2]:
                assert isinstance(arc, Part.ArcOfCircle)
                assert math.isclose(arc.EndPoint.x, -2, abs_tol=1e-6)
                tangent = arc.tangent(arc.LastParameter)[0]
                assert abs(tangent.y) < 1e-6, 'Relief does not meet flat tangentially'
            assert math.isclose(profile.Geometry[1].EndPoint.y-profile.Geometry[0].EndPoint.y, .5, abs_tol=1e-6)
        print('PASS: tangent side reliefs, 0.5 mm gap at the flat, no triangular remnant.')
        assert math.isclose(doc.LeftFlexureSlot.Length.Value, .5, abs_tol=1e-6)
        assert math.isclose(doc.RightFlexureSlot.Length.Value, .5, abs_tol=1e-6)
        gap_cell = doc.Parameters.getCellFromAlias('FlexGap')
        doc.Parameters.set(gap_cell, '0.6 mm')
        doc.recompute()
        assert math.isclose(doc.LeftFlexureSlot.Length.Value, .6, abs_tol=1e-6)
        assert math.isclose(doc.RightFlexureSlot.Length.Value, .6, abs_tol=1e-6)
        assert bodies[0].Shape.isValid() and len(bodies[0].Shape.Solids) == 1
        doc.Parameters.set(gap_cell, '0.5 mm')
        doc.recompute()
        print('PASS: original 0.5 mm lower-pivot flex gaps restored.')

        for label in ('Left', 'Right'):
            for suffix in ('PivotProfile', 'SocketProfile', 'BottomCornerProfile'):
                s = doc.getObject(label+suffix)
                arc = s.Geometry[0]
                assert isinstance(arc, Part.ArcOfCircle), s.Name
                assert 0 < arc.LastParameter-arc.FirstParameter <= math.pi/2+1e-6, s.Name
        assert any(isinstance(f.Surface, Part.Sphere) for f in bodies[0].Shape.Faces), 'Pivot still faceted'
        radius_cell = doc.Parameters.getCellFromAlias('PivotRadius')
        doc.Parameters.set(radius_cell, '2.55 mm')
        doc.recompute()
        for obj in doc.Objects:
            assert 'Invalid' not in obj.State, (obj.Name, obj.State)
        assert math.isclose(doc.LeftPivotProfile.Geometry[0].Radius, 2.55, abs_tol=1e-6)
        assert bodies[0].Shape.isValid() and len(bodies[0].Shape.Solids) == 1
        doc.Parameters.set(radius_cell, '2.5 mm')
        doc.recompute()
        print('PASS: analytic corner arcs and spherical pivots; aligned lower slot/relief junctions.')

        assert doc.getObject('OpeningBackSlope') is None, 'Rectangular opening notch remains'
        arcs = [g for g in doc.BackOutline.Geometry if isinstance(g, Part.ArcOfCircle)]
        assert len(arcs) == 2
        for arc in arcs:
            assert math.isclose(arc.Radius, 4, abs_tol=1e-6)
            assert math.isclose(arc.LastParameter-arc.FirstParameter, math.pi/2, abs_tol=1e-6)
        assert len(doc.OpeningShoulders.Base[1]) == 2
        assert len(doc.OpeningRim.Base[1]) == 3
        assert bodies[0].Shape.isInside(App.Vector(0, -4, 30), 1e-6, True), 'Central notch remains'
        for alias, changed, original in [('OpeningShoulderRadius', '0.9 mm', '1 mm'),
                                          ('OpeningRimRadius', '0.4 mm', '0.5 mm')]:
            initial_volume = bodies[0].Shape.Volume
            cell = doc.Parameters.getCellFromAlias(alias)
            doc.Parameters.set(cell, changed)
            doc.recompute()
            assert abs(bodies[0].Shape.Volume-initial_volume) > .001, alias
            for obj in doc.Objects:
                assert 'Invalid' not in obj.State, (obj.Name, obj.State)
            assert bodies[0].Shape.isValid() and len(bodies[0].Shape.Solids) == 1
            doc.Parameters.set(cell, original)
            doc.recompute()
        print('PASS: continuous R4 opening, R1 shoulders, R0.5 rim; no rectangular floor notch.')

        assert len(doc.GripChamfer.Base[1]) == 3
        assert len(doc.UpperGripChamfer.Base[1]) == 4
        assert doc.GripChamfer.Shape.Volume < doc.OpeningRim.Shape.Volume
        assert bodies[0].Shape.Volume < doc.GripChamfer.Shape.Volume
        for alias, changed, original in [('GripChamfer', '0.25 mm', '0.3 mm'),
                                          ('UpperGripChamfer', '0.1 mm', '0.15 mm')]:
            initial_volume = bodies[0].Shape.Volume
            cell = doc.Parameters.getCellFromAlias(alias)
            doc.Parameters.set(cell, changed)
            doc.recompute()
            assert bodies[0].Shape.Volume > initial_volume+.001, alias
            for obj in doc.Objects:
                assert 'Invalid' not in obj.State, (obj.Name, obj.State)
            assert bodies[0].Shape.isValid() and len(bodies[0].Shape.Solids) == 1
            doc.Parameters.set(cell, original)
            doc.recompute()
        print('PASS: exposed grip perimeter chamfers; pin and lower flex dimensions preserved.')

        # Upper arms remain tied to the rear plate: no added upper flex cuts.
        for side, label in ((-1, 'Left'), (1, 'Right')):
            for feature in ('UpperFlexIsolation', 'UpperFlexNeck'):
                assert doc.getObject(label+feature) is None
            assert bodies[0].Shape.isInside(App.Vector(side*10.35, -3, 31), 1e-6, True), 'Upper isolation slot still open'
            assert bodies[0].Shape.isInside(App.Vector(side*14.8, 0, 28), 1e-6, True), 'Upper outer relief still open'
        latch_volume = bodies[0].Shape.Volume
        initial_volume = bodies[2].Shape.Volume
        width_cell = doc.Parameters.getCellFromAlias('TopCatchWidth')
        doc.Parameters.set(width_cell, '15.4 mm')
        doc.recompute()
        assert bodies[2].Shape.Volume > initial_volume+.1, 'TopCatchWidth does not drive receiver'
        assert math.isclose(doc.TopCatchProfile.Placement.Base.x, -7.7, abs_tol=1e-6)
        assert math.isclose(doc.LeftTipReceiverProfile.Placement.Base.x, -7.71, abs_tol=1e-6)
        assert math.isclose(doc.RightTipReceiverProfile.Placement.Base.x, 4.7, abs_tol=1e-6)
        assert math.isclose(bodies[0].Shape.Volume, latch_volume, abs_tol=1e-5), 'Receiver width changed latch'
        for obj in doc.Objects:
            assert 'Invalid' not in obj.State, (obj.Name, obj.State)
        assert bodies[2].Shape.isValid() and len(bodies[2].Shape.Solids) == 1
        doc.Parameters.set(width_cell, '15.3 mm')
        doc.recompute()
        print('PASS: solid upper arms; receiver width drives block and socket positions; lower flex gaps unchanged.')

        # The snap lead-in calibration must change geometry and recompute cleanly.
        previous = bodies[0].Shape.Volume
        cell = doc.Parameters.getCellFromAlias('HookLeadIn')
        doc.Parameters.set(cell, '0.3 mm')
        doc.recompute()
        for obj in doc.Objects:
            assert 'Invalid' not in obj.State, (obj.Name, obj.State)
        assert bodies[0].Shape.Volume > previous+.01, 'HookLeadIn does not drive geometry'
        doc.Parameters.set(cell, '0.35 mm')
        doc.recompute()
        assert bodies[0].Shape.isValid()

        ns = {'m': 'http://schemas.microsoft.com/3dmanufacturing/core/2015/02'}
        with ZipFile(SOURCE) as archive:
            xml = ET.fromstring(archive.read('3D/Objects/object_4.model'))
        vertices = [App.Vector(float(v.attrib['x']), float(v.attrib['y']),
                               float(v.attrib['z'])+19.98223304748535)
                    for v in xml.findall('.//m:vertex', ns)]
        faces = [tuple(int(t.attrib[k]) for k in ('v1', 'v2', 'v3'))
                 for t in xml.findall('.//m:triangle', ns)]
        mesh = Mesh.Mesh([tuple(vertices[i] for i in tri) for tri in faces])
        # Deterministic source vertices; distance to reconstructed BRep, not vertex-to-vertex.
        distances = [bodies[0].Shape.distToShape(Part.Vertex(p))[0] for p in vertices[::4]]
        ordered = sorted(distances)
        report = {'samples': len(distances), 'source_volume_mm3': mesh.Volume,
                  'reconstructed_volume_mm3': bodies[0].Shape.Volume,
                  'source_to_cad_mean_mm': sum(distances)/len(distances),
                  'source_to_cad_p95_mm': ordered[int(.95*(len(ordered)-1))],
                  'source_to_cad_max_mm': max(distances),
                  'note': 'One-way sampled error, not symmetric Hausdorff distance or fit certification.'}
        print('COMPARISON:', json.dumps(report, indent=2), flush=True)
        assert all(math.isfinite(d) for d in distances)
        assert max(distances) < 5, 'Reconstruction departed from reference envelope'
        print('PASS: constrained editable sketches, single solids, no closed-assembly collision.')
        print('PASS: HookLeadIn parameter changes geometry. Reconstruction error is reported above.')
    finally:
        App.closeDocument(doc.Name)


if __name__ == '__main__':
    main()
