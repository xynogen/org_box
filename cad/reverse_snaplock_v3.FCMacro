"""Parametric reconstruction study of one SnapLock V3 latch and mating coupons.

Run in FreeCAD. The source 3MF is read only; organizer models are not changed.
Dimensions are measured from its mesh, not the author's original CAD history.
Output: reverse_snaplock_v3.FCStd. Edit the Parameters spreadsheet, then recompute.
"""
from pathlib import Path
import math

OUTPUT = Path(__file__).resolve().parents[1] / 'reverse_snaplock_v3.FCStd'


def build():
    import FreeCAD as App
    import Part
    import Sketcher

    V = App.Vector
    C = Sketcher.Constraint
    doc = App.newDocument('Reverse_SnapLock_V3')
    settings = doc.addObject('Spreadsheet::Sheet', 'Parameters')
    for row, (alias, value) in enumerate([
        ('Width', '30 mm'), ('Height', '39.964466 mm'), ('Thickness', '10 mm'),
        ('BackThickness', '3 mm'), ('FlexGap', '0.5 mm'),
        ('PivotRadius', '2.5 mm'), ('SocketClearance', '0.2 mm'),
        ('TipRadius', '2.5 mm'), ('TopTipClearance', '0.15 mm'),
        ('TopCatchWidth', '15.3 mm'),
        ('HookLeadIn', '0.35 mm'),
        ('SocketRoofRise', '2 mm'),
        ('TopEntryWidth', '11.6 mm'),
        ('EntryEdgeChamfer', '0.1 mm'),
        ('OpeningShoulderRadius', '1 mm'), ('OpeningRimRadius', '0.5 mm'),
        ('GripChamfer', '0.3 mm'), ('UpperGripChamfer', '0.15 mm'),
    ], 1):
        settings.set(f'A{row}', alias)
        settings.set(f'B{row}', value)
        settings.setAlias(f'B{row}', alias)
    settings.setColumnWidth('A', 170)
    settings.setColumnWidth('B', 100)
    doc.recompute()

    def sketch(owner, name, plane='XZ', offset=0, origin=None):
        s = owner.newObject('Sketcher::SketchObject', name)
        if plane == 'XZ':
            rotation = App.Rotation(V(1, 0, 0), V(0, 0, 1), V(0, -1, 0), 'ZXY')
            position = V(0, offset, 0)
        elif plane == 'YZ':
            rotation = App.Rotation(V(0, 1, 0), V(0, 0, 1), V(1, 0, 0), 'ZXY')
            position = V(offset, 0, 0)
        else:
            rotation = App.Rotation()
            position = V(0, 0, offset)
        s.Placement = App.Placement(origin if origin is not None else position, rotation)
        return s

    def dimension(s, con, expression=None):
        index = s.addConstraint(con)
        if expression is not None:
            s.setExpression(f'Constraints[{index}]', expression)

    def expression(value, axis):
        parameter, nominal = {'x': ('Width', 30), 'y': ('Thickness', 10),
                              'z': ('Height', 39.964466)}[axis]
        return f'Parameters.{parameter} * ({value / nominal:.12g})'

    def point(s, geometry, endpoint, x, y, axes):
        for kind, value, axis in [('DistanceX', x, axes[0]), ('DistanceY', y, axes[1])]:
            # Zero coordinates use native dimensions without expressions.
            if abs(value) < 1e-10:
                s.addConstraint(C(kind, geometry, endpoint, 0.0))
            else:
                dimension(s, C(kind, geometry, endpoint, value), expression(value, axis))

    def polygon(s, points, axes):
        for a, b in zip(points, points[1:] + points[:1]):
            i = s.addGeometry(Part.LineSegment(V(*a, 0), V(*b, 0)), False)
            point(s, i, 1, *a, axes)
            point(s, i, 2, *b, axes)

    def circle(s, center, radius, axes, radius_expression):
        i = s.addGeometry(Part.Circle(V(*center, 0), V(0, 0, 1), radius), False)
        point(s, i, 3, *center, axes)
        dimension(s, C('Radius', i, radius), radius_expression)

    def finish(owner, s, kind, name, length=None, reversed=False):
        doc.recompute()
        if not s.FullyConstrained or s.solve() != 0:
            raise RuntimeError(f'{s.Name}: sketch is not fully constrained')
        previous = owner.Tip
        f = owner.newObject('PartDesign::'+kind, name)
        f.Profile = s
        if kind in ('Revolution', 'Groove'):
            f.ReferenceAxis = (s, ['H_Axis'])
            f.Angle = 360
        else:
            f.Length = length
            f.Reversed = reversed
        doc.recompute()
        if f.Shape.isNull() or not f.Shape.isValid() or len(f.Shape.Solids) != 1:
            raise RuntimeError(f'{name}: {f.getStatusString()} (invalid or disconnected solid)')
        if previous is not None:
            previous.Visibility = False
        s.Visibility = False
        f.Visibility = True
        return f

    latch = doc.addObject('PartDesign::Body', 'Latch')
    latch.Label = '01 Reconstructed latch — dimensional sketches'
    s = sketch(latch, 'BackOutline', offset=-2)
    # Tangent R4 corners form the finger opening, not a polygonal approximation.
    points = [(-15, 0), (15, 0), (15, 40), (8, 40), (8, 35)]
    for a, b in zip(points, points[1:]):
        i = s.addGeometry(Part.LineSegment(V(*a, 0), V(*b, 0)), False)
        point(s, i, 1, *a, 'xz')
        point(s, i, 2, *b, 'xz')
    for side in (1, -1):
        angles = (-math.pi/2, 0) if side > 0 else (math.pi, 3*math.pi/2)
        g = s.addGeometry(Part.ArcOfCircle(Part.Circle(V(side*4, 35, 0), V(0, 0, 1), 4), *angles), False)
        s.addConstraint([C('DistanceX', g, 3, side*4), C('DistanceY', g, 3, 35),
                         C('Radius', g, 4), C('Angle', g, math.pi/2),
                         C('DistanceX' if side > 0 else 'DistanceY', g, 1, 4 if side > 0 else 35)])
    points = [(4, 31), (-4, 31)]
    for a, b in [(points[0], points[1]), ((-8, 35), (-8, 40)),
                 ((-8, 40), (-15, 40)), ((-15, 40), (-15, 0))]:
        i = s.addGeometry(Part.LineSegment(V(*a, 0), V(*b, 0)), False)
        point(s, i, 1, *a, 'xz')
        point(s, i, 2, *b, 'xz')
    back = finish(latch, s, 'Pad', 'BackPlate', 3)
    back.setExpression('Length', 'Parameters.BackThickness')

    # Lower arms, with their roots at the bottom of the rear plate.
    for side, label in ((-1, 'Left'), (1, 'Right')):
        s = sketch(latch, label+'LowerArmProfile', 'YZ', side*12 if side > 0 else -15)
        polygon(s, [(-5, 0), (-2, 0), (5, 12.124), (5, 14),
                    (3, 18), (3, 20), (-2, 20), (-5, 21.69)], 'yz')
        finish(latch, s, 'Pad', label+'LowerArm', 3)

        # U-shaped upper arms leave the central finger opening clear.
        s = sketch(latch, label+'UpperArmOutline', offset=5)
        pts = [(side*x, z) for x, z in [(10.75, 20.5), (15, 20.5), (15, 40),
                                        (8, 40), (8, 35), (10.75, 32.25)]]
        polygon(s, pts, 'xz')
        finish(latch, s, 'Pad', label+'UpperArm', 7)

    # This tapered web is distinct from the two flexing side arms.
    s = sketch(latch, 'CentralWebProfile', 'YZ', -3.4)
    polygon(s, [(-2, 0.27), (4.3, 15.4), (3, 18), (-2, 18)], 'yz')
    finish(latch, s, 'Pad', 'CentralWeb', 6.8)
    s = sketch(latch, 'CentralNeckProfile', 'YZ', -1)
    polygon(s, [(-2, 18), (3, 18), (3, 22), (3.946, 23.892), (-2, 30.66)], 'yz')
    finish(latch, s, 'Pad', 'CentralNeck', 2)

    # Global side silhouette: 45-degree upper lead-in and rounded tip envelope.
    s = sketch(latch, 'TopLeadInProfile', 'YZ', -16)
    polygon(s, [(-6, 32.5), (1.8, 40.3), (1.8, 45), (-6, 45)], 'yz')
    finish(latch, s, 'Pocket', 'TopLeadIn', 32, reversed=True)
    for side, label in ((-1, 'Left'), (1, 'Right')):
        s = sketch(latch, label+'UpperArmLeadInProfile', 'YZ', -15.01 if side < 0 else 10.74)
        polygon(s, [(3, 20.49), (5.01, 20.49), (5.01, 26.02), (3, 22)], 'yz')
        finish(latch, s, 'Pocket', label+'UpperArmLeadIn', 4.27, reversed=True)

    # Keep a continuous rounded floor; the old back-slope pocket left a rectangular notch.

    # Analytic quarter circles avoid faceted lower corners.
    for side, label in ((-1, 'Left'), (1, 'Right')):
        s = sketch(latch, label+'BottomCornerProfile', offset=5.01)
        start, end = ((9, 0), (15, 6)) if side > 0 else ((-15, 6), (-9, 0))
        angles = (-math.pi/2, 0) if side > 0 else (math.pi, 3*math.pi/2)
        g = s.addGeometry(Part.ArcOfCircle(Part.Circle(V(side*9, 6, 0), V(0, 0, 1), 6), *angles), False)
        s.addConstraint([C('DistanceX', g, 3, side*9), C('DistanceY', g, 3, 6),
                         C('Radius', g, 6), C('DistanceX' if side > 0 else 'DistanceY', g, 1, 9 if side > 0 else 6),
                         C('DistanceY' if side > 0 else 'DistanceX', g, 2, 6 if side > 0 else -9)])
        points = [end, (side*15, 0), start]
        for a, b in zip(points, points[1:]):
            i = s.addGeometry(Part.LineSegment(V(*a, 0), V(*b, 0)), False)
            point(s, i, 1, *a, 'xz')
            point(s, i, 2, *b, 'xz')
        finish(latch, s, 'Pocket', label+'BottomCorner', 10.02, reversed=True)

    # End the lower slots at the relief underside, not above it (which left a notch).
    def relief_arc(s, lift=0):
        # Tangent to the flat arm at Y=-2; the same curve caps the vertical slot.
        radius = 3.5
        sweep = math.asin(3.01/radius)
        center_z = 23.5+lift
        g = s.addGeometry(Part.ArcOfCircle(Part.Circle(V(-2, center_z, 0), V(0, 0, 1), radius),
                                          -math.pi/2-sweep, -math.pi/2), False)
        s.addConstraint([C('DistanceX', g, 3, -2), C('DistanceY', g, 3, center_z),
                         C('Radius', g, radius), C('Angle', g, sweep), C('DistanceX', g, 1, -5.01)])
        return (-5.01, center_z-math.sqrt(radius**2-3.01**2)), (-2, 20+lift)

    def relief_lines(s, points):
        for a, b in zip(points, points[1:]):
            i = s.addGeometry(Part.LineSegment(V(*a, 0), V(*b, 0)), False)
            for endpoint, (x, y) in enumerate((a, b), 1):
                s.addConstraint([C('DistanceX', i, endpoint, x), C('DistanceY', i, endpoint, y)])

    for side, label in ((-1, 'Left'), (1, 'Right')):
        s = sketch(latch, label+'FlexureSlotProfile', 'YZ', -12 if side < 0 else 11.5)
        s.setExpression('Placement.Base.x', '-Parameters.Width * 0.4' if side < 0
                        else 'Parameters.Width * 0.4 - Parameters.FlexGap')
        back_point, tangent = relief_arc(s)
        relief_lines(s, [tangent, (3, 20), (5.01, 20), (5.01, 6.3),
                         (-5.01, 6.3), back_point])
        slot = finish(latch, s, 'Pocket', label+'FlexureSlot', .5, reversed=True)
        slot.setExpression('Length', 'Parameters.FlexGap')
    for side, label in ((-1, 'Left'), (1, 'Right')):
        s = sketch(latch, label+'FlexureReliefProfile', 'YZ', -15.01 if side < 0 else 11.5)
        lower_back, lower_tangent = relief_arc(s)
        upper_back, upper_tangent = relief_arc(s, .5)
        relief_lines(s, [lower_tangent, (3, 20), (3, 20.5), upper_tangent])
        relief_lines(s, [upper_back, lower_back])
        finish(latch, s, 'Pocket', label+'FlexureRelief', 3.51, reversed=True)

    # Upper arms stay solid; tune assembly fit with TopCatchWidth instead of flex cuts.

    def cap(owner, name, center_y, center_z, base_x, tip_x, radius, kind):
        # Revolve an analytic circular meridian for a smooth spherical pin/socket.
        s = sketch(owner, name+'Profile', 'XY', origin=V(0, center_y, center_z))
        center_x = 13.264724735 if base_x > 0 else -13.264724735
        radius_expr = 'Parameters.PivotRadius'+(' + Parameters.SocketClearance' if kind == 'Groove' else '')
        arc_start, arc_end = sorted((base_x, tip_x), reverse=True)
        angles = [math.acos((x-center_x)/radius) for x in (arc_start, arc_end)]
        g = s.addGeometry(Part.ArcOfCircle(Part.Circle(V(center_x, 0, 0), V(0, 0, 1), radius), *angles), False)
        s.addConstraint([C('DistanceX', g, 3, center_x), C('DistanceY', g, 3, 0.0),
                         C('Radius', g, radius), C('DistanceX', g, 1, arc_start),
                         C('Angle', g, angles[1]-angles[0])])
        s.setExpression('Constraints[2]', radius_expr)
        s.setExpression('Constraints[4]',
                        f'acos(({arc_end-center_x} mm)/({radius_expr})) - acos(({arc_start-center_x} mm)/({radius_expr}))')
        points = [(arc_end, math.sqrt(radius**2-(arc_end-center_x)**2)),
                  (arc_end, 0), (arc_start, 0),
                  (arc_start, math.sqrt(radius**2-(arc_start-center_x)**2))]
        for a, b in zip(points, points[1:]):
            i = s.addGeometry(Part.LineSegment(V(*a, 0), V(*b, 0)), False)
            for endpoint, (x, y) in enumerate((a, b), 1):
                s.addConstraint(C('DistanceX', i, endpoint, x))
                dimension(s, C('DistanceY', i, endpoint, y),
                          f'sqrt(({radius_expr})^2 - {((x-center_x)**2):.15g} mm^2)' if y else None)
        return finish(owner, s, kind, name)

    for side, label in ((-1, 'Left'), (1, 'Right')):
        cap(latch, label+'Pivot', .5, 17.5, side*12, side*10.8, 2.5, 'Revolution')

    # Inward-facing upper tips, separate from the lower ball pivots.
    for side, label in ((-1, 'Left'), (1, 'Right')):
        s = sketch(latch, label+'HookTipProfile', 'YZ', side*6 if side > 0 else -8.2)
        circle(s, (2.5, 37.5), 2.5, 'yz', 'Parameters.TipRadius')
        finish(latch, s, 'Pad', label+'HookTip', 2.2)
    previous = latch.Tip
    edges = [f'Edge{i+1}' for i, edge in enumerate(previous.Shape.Edges)
             if isinstance(edge.Curve, Part.Circle)
             and abs(abs(edge.CenterOfMass.x)-6) < 1e-5
             and abs(edge.CenterOfMass.z-37.5) < 1e-5]
    hook_lead_in = latch.newObject('PartDesign::Chamfer', 'HookLeadIn')
    hook_lead_in.Base = (previous, edges)
    hook_lead_in.Size = 0.8
    hook_lead_in.setExpression('Size', 'Parameters.HookLeadIn')
    doc.recompute()
    if len(edges) != 2 or hook_lead_in.Shape.isNull() or not hook_lead_in.Shape.isValid():
        raise RuntimeError('HookLeadIn: could not chamfer both snap tips')
    previous.Visibility = False

    # Blend the two inner shoulders, away from pins and the lower flexure slots.
    previous = latch.Tip
    edges = [f'Edge{i+1}' for i, edge in enumerate(previous.Shape.Edges)
             if abs(abs(edge.CenterOfMass.x)-10.75) < 1e-5
             and abs(edge.CenterOfMass.z-32.25) < 1e-5 and abs(edge.Length-7) < 1e-5]
    if len(edges) != 2:
        raise RuntimeError('OpeningShoulders: expected two inner shoulders')
    rounded = latch.newObject('PartDesign::Fillet', 'OpeningShoulders')
    rounded.Base = (previous, edges)
    rounded.Radius = 1
    rounded.setExpression('Radius', 'Parameters.OpeningShoulderRadius')
    doc.recompute()
    if rounded.Shape.isNull() or not rounded.Shape.isValid() or len(rounded.Shape.Solids) != 1:
        raise RuntimeError('OpeningShoulders: invalid fillet')
    previous.Visibility = False

    previous = latch.Tip
    edges = [f'Edge{i+1}' for i, edge in enumerate(previous.Shape.Edges)
             if abs(edge.CenterOfMass.y+5) < 1e-5
             and 30.9 < edge.CenterOfMass.z < 33 and abs(edge.CenterOfMass.x) < 7]
    if len(edges) != 3:
        raise RuntimeError('OpeningRim: expected continuous U-shaped rim')
    rounded = latch.newObject('PartDesign::Fillet', 'OpeningRim')
    rounded.Base = (previous, edges)
    rounded.Radius = .5
    rounded.setExpression('Radius', 'Parameters.OpeningRimRadius')
    doc.recompute()
    if rounded.Shape.isNull() or not rounded.Shape.isValid() or len(rounded.Shape.Solids) != 1:
        raise RuntimeError('OpeningRim: invalid fillet')
    previous.Visibility = False

    # Break only the exposed back-face perimeter, not pin or slot edges.
    for name, size, lower in [('GripChamfer', .3, True), ('UpperGripChamfer', .15, False)]:
        previous = latch.Tip
        edges = []
        for i, edge in enumerate(previous.Shape.Edges):
            bb, center = edge.BoundBox, edge.CenterOfMass
            on_back = abs(bb.YMin+5) < 1e-5 and abs(bb.YMax+5) < 1e-5
            selected = center.z < 6.1 if lower else (
                (abs(abs(center.x)-15) < 1e-5 and center.z > 22.3)
                or (center.z > 33.4 and abs(center.x) > 10))
            if on_back and selected:
                edges.append(f'Edge{i+1}')
        if len(edges) != (3 if lower else 4):
            raise RuntimeError(f'{name}: unexpected grip perimeter')
        softened = latch.newObject('PartDesign::Chamfer', name)
        softened.Base = (previous, edges)
        softened.Size = size
        softened.setExpression('Size', f'Parameters.{name}')
        doc.recompute()
        if softened.Shape.isNull() or not softened.Shape.isValid() or len(softened.Shape.Solids) != 1:
            raise RuntimeError(f'{name}: invalid grip chamfer')
        previous.Visibility = False

    base = doc.addObject('PartDesign::Body', 'BaseCoupon')
    base.Label = '02 Base mounting coupon — twin spherical sockets'
    s = sketch(base, 'BaseWallProfile', 'YZ', -18)
    polygon(s, [(5, -5), (7, -5), (7, 20), (3, 20), (3, 18), (5, 14)], 'yz')
    finish(base, s, 'Pad', 'BaseWall', 36)
    for side, label in ((-1, 'Left'), (1, 'Right')):
        s = sketch(base, label+'SocketRootProfile', 'YZ', -11.8 if side < 0 else 7.2)
        polygon(s, [(5, 9), (-2, 16), (-2, 20), (5, 20)], 'yz')
        finish(base, s, 'Pad', label+'SocketRoot', 4.6)
        cap(base, label+'Socket', .5, 17.5, side*11.8, side*10.6, 2.7, 'Groove')

    top = doc.addObject('PartDesign::Body', 'TopCoupon')
    top.Label = '03 Top engagement coupon — fork receivers'
    s = sketch(top, 'TopWallProfile', 'YZ', -18)
    polygon(s, [(3, 20), (7, 20), (7, 40), (5, 40), (5, 26), (3, 22)], 'yz')
    finish(top, s, 'Pad', 'TopWall', 36)
    s = sketch(top, 'TopCatchProfile', 'YZ', -7.5)
    s.setExpression('Placement.Base.x', '-Parameters.TopCatchWidth / 2')
    polygon(s, [(5, 26), (5, 30), (2.5, 29.7), (0, 30.1), (-2, 31.15),
                (-2, 37), (5, 44), (7, 45), (7, 37), (5, 35)], 'yz')
    # Raise the sloping roof outward; keep the pin centre, bore and mating width unchanged.
    for line, endpoint, original_z in [(4, 2, 37), (5, 1, 37), (5, 2, 44),
                                       (6, 1, 44), (6, 2, 45), (7, 1, 45)]:
        s.setExpression(f'Constraints[{line*4+(endpoint-1)*2+1}]',
                        f'{original_z} mm + Parameters.SocketRoofRise')
    catch = finish(top, s, 'Pad', 'TopCatch', 15)
    catch.setExpression('Length', 'Parameters.TopCatchWidth')
    for side, label in ((-1, 'Left'), (1, 'Right')):
        s = sketch(top, label+'TipReceiverProfile', 'YZ', -7.51 if side < 0 else 4.5)
        s.setExpression('Placement.Base.x', '-Parameters.TopCatchWidth/2 - 0.01 mm' if side < 0
                        else 'Parameters.TopCatchWidth/2 - 3 mm')
        circle(s, (2.5, 37.5), 2.9, 'yz', 'Parameters.TipRadius + Parameters.TopTipClearance')
        finish(top, s, 'Pocket', label+'TipReceiver', 3.01, reversed=True)
    # Taper the free nose toward the sockets, not the seated socket walls.
    for side, label in ((-1, 'Left'), (1, 'Right')):
        s = sketch(top, label+'EntryRampProfile', 'XY', 48)
        polygon(s, [(side*x, y) for x, y in [
            (5.8, -2.01), (7.65, -.3), (8.65, -.3), (8.65, -3), (5.8, -3)]], 'xy')
        for line, endpoint, value in [(0, 1, 'Parameters.TopEntryWidth/2'),
                                      (0, 2, 'Parameters.TopCatchWidth/2'),
                                      (1, 1, 'Parameters.TopCatchWidth/2'),
                                      (1, 2, 'Parameters.TopCatchWidth/2 + 1 mm'),
                                      (2, 1, 'Parameters.TopCatchWidth/2 + 1 mm'),
                                      (2, 2, 'Parameters.TopCatchWidth/2 + 1 mm'),
                                      (3, 1, 'Parameters.TopCatchWidth/2 + 1 mm'),
                                      (3, 2, 'Parameters.TopEntryWidth/2'),
                                      (4, 1, 'Parameters.TopEntryWidth/2'),
                                      (4, 2, 'Parameters.TopEntryWidth/2')]:
            s.setExpression(f'Constraints[{line*4+(endpoint-1)*2}]', f'({side}) * ({value})')
        finish(top, s, 'Pocket', label+'EntryRamp', 30)
    # Sketch the corner breaks so changing roof/width does not lose dress-up edge links.
    for side, label in ((-1, 'Left'), (1, 'Right')):
        s = sketch(top, label+'EntryCornerProfile', 'XY', 48)
        polygon(s, [(side*7.65, -.3), (side*7.55, -.3924324324),
                    (side*7.65, -.2)], 'xy')
        for line, endpoint in [(0, 1), (1, 2), (2, 1), (2, 2)]:
            s.setExpression(f'Constraints[{line*4+(endpoint-1)*2}]',
                            f'({side}) * Parameters.TopCatchWidth/2')
        for line, endpoint in [(0, 2), (1, 1)]:
            s.setExpression(f'Constraints[{line*4+(endpoint-1)*2}]',
                            f'({side}) * (Parameters.TopCatchWidth/2 - Parameters.EntryEdgeChamfer)')
            s.setExpression(f'Constraints[{line*4+(endpoint-1)*2+1}]',
                            '-0.3 mm - Parameters.EntryEdgeChamfer * 1.71 mm / ((Parameters.TopCatchWidth - Parameters.TopEntryWidth)/2)')
        for line, endpoint in [(1, 2), (2, 1)]:
            s.setExpression(f'Constraints[{line*4+(endpoint-1)*2+1}]',
                            '-0.3 mm + Parameters.EntryEdgeChamfer')
        finish(top, s, 'Pocket', label+'EntryCorner', 30)
    # Keep square socket mouths for retention; the pin tips provide the insertion lead-in.

    for owner, color in [(latch, (.88, .65, .3)), (base, (.35, .6, .8)), (top, (.45, .75, .5))]:
        for obj in owner.Group:
            if hasattr(obj, 'Visibility'):
                obj.Visibility = obj == owner.Tip
        owner.Visibility = True
        if App.GuiUp:
            owner.Tip.ViewObject.ShapeColor = color
    doc.recompute()
    doc.saveAs(str(OUTPUT))
    if App.GuiUp:
        import FreeCADGui as Gui
        Gui.activeDocument().activeView().viewAxonometric()
        Gui.activeDocument().activeView().fitAll()
    print('BUILT:', OUTPUT)
    print('Study model only: compare against source before using this latch in the organizer.')


if __name__ == '__main__':
    build()
