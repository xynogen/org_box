"""Geometry generation only. Run with FreeCAD: Macro > Macros > Execute.
Edit the dimensions below, then rerun. Each run creates a new document.
Checks: python cad/test_organizer_a1mini.FCMacro --check (dimensions only).
Outputs: root-level FCStd models and print-oriented files in stl/.
"""
from pathlib import Path
import math

# Dimensions in mm. Outer length includes room for a 3 mm brim on A1 Mini.
LENGTH = 170.0
WIDTH = 115.5
HEIGHT = 75.0
WALL = 3.0
FLOOR = 3.0
LID_THICKNESS = 3.6
TOOL_WIDTH = 32.6
TOOL_LENGTH = 70.0
TOOL_THICKNESS = 15.0  # Initial assumption: measure the real tool before printing.
TOOL_CLEARANCE = 0.4  # Clearance on each side.
PIN_DIAMETER = 1.75
PIN_HOLE = 2.1  # Calibration knob: adjust after a small printer-fit test.
HINGE_RADIUS = 4.0
HINGE_SPAN = 150.0
HINGE_GAP = 0.5
HINGE_SEGMENT = (HINGE_SPAN-4*HINGE_GAP)/5
HINGE_STARTS = tuple(-HINGE_SPAN/2+i*(HINGE_SEGMENT+HINGE_GAP) for i in range(5))
ASSEMBLY_GAP = 0.4
BRIM = 3.0
TRAY_GAP = 0.5  # Removable bento trays: clearance to shell and to each other.
TRAY_WALL = 2.4
TRAY_HEIGHT = 68.0
LATCH_PIN_HOLE = 2.1  # Front pivot uses the same 1.75 mm filament as the rear hinge.
LATCH_PIVOT_CLEARANCE = 0.3  # Clearance between latch and pivot ears.
CABLE_DIAMETER = 5.0  # Measure the cable jacket, not its connector.
CABLE_CLEARANCE = 0.2  # Radial clearance inside each channel.
CABLE_MOUTH = 4.6  # Small jacket compression; PLA is not a flexible spring.
CABLE_CLIP_HEIGHT = 8.0
BOTTOM_CHAMFER = 0.8  # 45-degree bottom edge; leaves the center flat for printing.
RIM_FILLET = 0.6  # Small enough to preserve the 2.4 mm tray walls.
STACK_CLEARANCE = 0.35  # Per side between the locating rib and bottom groove.
STACK_RIB_HEIGHT = 0.8
STACK_GROOVE_DEPTH = 1.0
STACK_RIB_WIDTH = 2.0
OUTPUT = Path(__file__).resolve().parents[1]


def build():
    import FreeCAD as App
    import Part
    import Sketcher
    import MeshPart

    doc = App.newDocument('Organizer_A1Mini')
    doc.Label = f'Organizer PLA {LENGTH:g} x {WIDTH:g} x {HEIGHT:g} — A1 Mini'
    V = App.Vector
    half_w = WIDTH / 2
    hinge_y = half_w + HINGE_RADIUS
    axis_z = HEIGHT
    lid_bottom = HEIGHT + ASSEMBLY_GAP
    sketches = []

    def sketch(owner, name, z=0, x=None):
        s = owner.Document.addObject('Sketcher::SketchObject', name)
        owner.addObject(s)
        if x is None:
            s.Placement = App.Placement(V(0, 0, z), App.Rotation())
        else:
            # Local sketch X/Y become world Y/Z; normal becomes world X.
            rotation = App.Rotation(V(0, 1, 0), V(0, 0, 1), V(1, 0, 0), 'ZXY')
            s.Placement = App.Placement(V(x, 0, 0), rotation)
        sketches.append(s)
        return s

    def fixed(s, geometry):
        i = s.addGeometry(geometry, False)
        s.addConstraint(Sketcher.Constraint('Block', i))

    def polygon(s, points):
        for a, b in zip(points, points[1:] + points[:1]):
            fixed(s, Part.LineSegment(V(*a, 0), V(*b, 0)))

    def rectangle(s, w, h, x=0, y=0):
        polygon(s, [(x-w/2, y-h/2), (x+w/2, y-h/2),
                    (x+w/2, y+h/2), (x-w/2, y+h/2)])

    def rounded_rectangle(s, w, h, radius, x=0, y=0):
        left, right = x-w/2, x+w/2
        bottom, top = y-h/2, y+h/2
        r = radius
        for a, b in [((left+r, bottom), (right-r, bottom)),
                     ((right, bottom+r), (right, top-r)),
                     ((right-r, top), (left+r, top)),
                     ((left, top-r), (left, bottom+r))]:
            fixed(s, Part.LineSegment(V(*a, 0), V(*b, 0)))
        for cx, cy, angle in [(right-r, bottom+r, -90), (right-r, top-r, 0),
                              (left+r, top-r, 90), (left+r, bottom+r, 180)]:
            fixed(s, Part.ArcOfCircle(Part.Circle(V(cx, cy, 0), V(0, 0, 1), r),
                                      math.radians(angle), math.radians(angle+90)))

    def circle(s, diameter, x, y):
        fixed(s, Part.Circle(V(x, y, 0), V(0, 0, 1), diameter/2))

    def feature(owner, s, length, name, cut=False, reversed=False):
        owner.Document.recompute()
        if not s.FullyConstrained:
            raise RuntimeError(f'{s.Name}: unconstrained sketch')
        previous = owner.Tip
        f = owner.newObject('PartDesign::Pocket' if cut else 'PartDesign::Pad', name)
        f.Profile = s
        f.Length = length
        f.Reversed = reversed
        owner.Document.recompute()
        if f.Shape.isNull() or not f.Shape.isValid() or len(f.Shape.Solids) != 1:
            raise RuntimeError(f'{name}: invalid solid ({f.getStatusString()})')
        s.Visibility = False
        if previous and previous != s:
            previous.Visibility = False
        f.Visibility = True
        return f

    def dress_edges(owner, kind, z, size, name):
        previous = owner.Tip
        edges = [f'Edge{i+1}' for i, e in enumerate(previous.Shape.Edges)
                 if abs(e.BoundBox.ZMin-z) < 1e-6 and abs(e.BoundBox.ZMax-z) < 1e-6]
        if not edges:
            raise RuntimeError(f'{name}: no planar perimeter edges at z={z:g}')
        f = owner.newObject('PartDesign::'+kind, name)
        f.Base = (previous, edges)
        if kind == 'Chamfer':
            f.Size = size
        else:
            f.Radius = size
        owner.Document.recompute()
        if f.Shape.isNull() or not f.Shape.isValid() or len(f.Shape.Solids) != 1:
            raise RuntimeError(f'{name}: invalid solid ({f.getStatusString()})')
        previous.Visibility = False
        f.Visibility = True
        return f

    base = doc.addObject('PartDesign::Body', 'Base')
    base.Label = '01 Base — tool, cables, accessories'
    s = sketch(base, 'OuterFootprint')
    rounded_rectangle(s, LENGTH, WIDTH, 8)
    feature(base, s, HEIGHT, 'OuterPad')
    s = sketch(base, 'InnerFootprint', z=HEIGHT)
    rounded_rectangle(s, LENGTH-2*WALL, WIDTH-2*WALL, 5)
    feature(base, s, HEIGHT-FLOOR, 'Cavity', cut=True)
    dress_edges(base, 'Chamfer', 0, BOTTOM_CHAMFER, 'BaseBottomChamfer')
    dress_edges(base, 'Fillet', HEIGHT, RIM_FILLET, 'BaseRimFillet')
    # Shallow underside groove leaves a flat load-bearing base and >=2 mm floor.
    s = sketch(base, 'StackBottomGrooveProfile')
    rounded_rectangle(s, LENGTH-12+2*STACK_CLEARANCE, WIDTH-12+2*STACK_CLEARANCE, 6+STACK_CLEARANCE)
    rounded_rectangle(s, LENGTH-12-2*STACK_RIB_WIDTH-2*STACK_CLEARANCE,
                      WIDTH-12-2*STACK_RIB_WIDTH-2*STACK_CLEARANCE,
                      6-STACK_RIB_WIDTH-STACK_CLEARANCE)
    feature(base, s, STACK_GROOVE_DEPTH, 'StackBottomGroove', cut=True, reversed=True)
    # 45-degree hinge roots avoid a thin unsupported ledge at the back.
    for n, start in enumerate(HINGE_STARTS[::2], 1):
        s = sketch(base, f'BaseHingeRootProfile{n}', x=start)
        polygon(s, [(half_w-3, HEIGHT-12), (half_w, HEIGHT-12),
                    (half_w+8, HEIGHT-4), (half_w+8, HEIGHT), (half_w-3, HEIGHT)])
        feature(base, s, HINGE_SEGMENT, f'BaseHingeRoot{n}')
        s = sketch(base, f'BaseKnuckleProfile{n}', x=start)
        circle(s, 2*HINGE_RADIUS, hinge_y, axis_z)
        feature(base, s, HINGE_SEGMENT, f'BaseKnuckle{n}')
    s = sketch(base, 'BasePinBoreProfile', x=-80)
    circle(s, PIN_HOLE, hinge_y, axis_z)
    feature(base, s, 160, 'BaseFilamentBore', cut=True, reversed=True)
    # Clear the central rim for the pinned latch's swing.
    s = sketch(base, 'LatchSwingReliefProfile', z=HEIGHT)
    rectangle(s, 36, 10, y=-half_w)
    feature(base, s, 10, 'LatchSwingRelief', cut=True)
    s = sketch(base, 'CatchRootProfile', x=-12)
    # The underside grows outwards at 45 degrees; no floating round bead.
    polygon(s, [(-half_w+1, HEIGHT-25.1), (-half_w, HEIGHT-25.1),
                (-half_w-4, HEIGHT-21.1), (-half_w-4, HEIGHT-20),
                (-half_w-5.1, HEIGHT-20), (-half_w-5.1, HEIGHT-19),
                (-half_w-3.5, HEIGHT-17.4), (-half_w+1, HEIGHT-17.4)])
    feature(base, s, 24, 'CatchRoot')

    lid = doc.addObject('PartDesign::Body', 'Lid')
    lid.Label = '02 Lid — filament-pin hinge'
    s = sketch(lid, 'LidFootprint', z=lid_bottom)
    rounded_rectangle(s, LENGTH, WIDTH, 8)
    feature(lid, s, LID_THICKNESS, 'LidPlate')
    dress_edges(lid, 'Fillet', lid_bottom+LID_THICKNESS, RIM_FILLET, 'LidOuterFillet')
    # Continuous locating rib enters the next box's underside groove.
    s = sketch(lid, 'StackTopRibProfile', z=lid_bottom+LID_THICKNESS)
    rounded_rectangle(s, LENGTH-12, WIDTH-12, 6)
    rounded_rectangle(s, LENGTH-12-2*STACK_RIB_WIDTH, WIDTH-12-2*STACK_RIB_WIDTH, 6-STACK_RIB_WIDTH)
    feature(lid, s, STACK_RIB_HEIGHT, 'StackTopRib')
    s = sketch(lid, 'AlignmentLipProfile', z=lid_bottom)
    rounded_rectangle(s, LENGTH-2*WALL-0.8, WIDTH-2*WALL-0.8, 4.6)
    rounded_rectangle(s, LENGTH-2*WALL-4, WIDTH-2*WALL-4, 3)
    feature(lid, s, 2, 'AlignmentLip', reversed=True)
    for n, start in enumerate(HINGE_STARTS[1::2], 1):
        s = sketch(lid, f'LidHingeRootProfile{n}', z=lid_bottom)
        rectangle(s, HINGE_SEGMENT, 11, x=start+HINGE_SEGMENT/2, y=half_w+2.5)
        feature(lid, s, LID_THICKNESS, f'LidHingeRoot{n}')
        s = sketch(lid, f'LidKnuckleProfile{n}', x=start)
        circle(s, 2*HINGE_RADIUS, hinge_y, axis_z)
        feature(lid, s, HINGE_SEGMENT, f'LidKnuckle{n}')
    s = sketch(lid, 'LidPinBoreProfile', x=-80)
    circle(s, PIN_HOLE, hinge_y, axis_z)
    feature(lid, s, 160, 'LidFilamentBore', cut=True, reversed=True)
    # Two supported ears replace the unsupported 26 mm integral axle.
    pivot_y, pivot_z = -half_w-1, HEIGHT-5
    for n, x in enumerate((-16.5, 12+LATCH_PIVOT_CLEARANCE), 1):
        s = sketch(lid, f'LatchPivotEarProfile{n}', x=x)
        polygon(s, [(-half_w+2, lid_bottom), (-half_w-2.5, lid_bottom),
                    (-half_w-3.5, lid_bottom-1), (-half_w-3.5, pivot_z-1.5),
                    (-half_w-2.5, pivot_z-2.5), (-half_w+0.5, pivot_z-2.5),
                    (-half_w+2, pivot_z-1)])
        feature(lid, s, 4.5-LATCH_PIVOT_CLEARANCE, f'LatchPivotEar{n}')
    s = sketch(lid, 'LatchPivotBoreProfile', x=-17)
    # Roof points down in assembly, up when the lid is printed upside down.
    r = LATCH_PIN_HOLE/2
    t = r/math.sqrt(2)
    fixed(s, Part.ArcOfCircle(Part.Circle(V(pivot_y, pivot_z, 0), V(0, 0, 1), r),
                              math.radians(-45), math.radians(225)))
    polygon_points = [(pivot_y-t, pivot_z-t), (pivot_y, pivot_z-r*math.sqrt(2)),
                      (pivot_y+t, pivot_z-t)]
    for a, b in zip(polygon_points, polygon_points[1:]):
        fixed(s, Part.LineSegment(V(*a, 0), V(*b, 0)))
    feature(lid, s, 34, 'LatchPivotBores', cut=True, reversed=True)

    latch = doc.addObject('PartDesign::Body', 'Latch')
    latch.Label = '03 Pinned snap-lock — print flat on its side'
    s = sketch(latch, 'SnapClipProfile', x=-12)
    circle(s, 7, pivot_y, pivot_z)
    circle(s, LATCH_PIN_HOLE, pivot_y, pivot_z)
    feature(latch, s, 24, 'SnapClipRing')
    # Constant X thickness puts the entire side profile on the print bed.
    s = sketch(latch, 'LatchPlateProfile', x=-12)
    polygon(s, [(-half_w-5.75, HEIGHT-13), (-half_w-3.25, HEIGHT-13),
                (-half_w-3.25, HEIGHT-5), (-half_w-5.75, HEIGHT-5)])
    feature(latch, s, 24, 'LatchPlate')
    s = sketch(latch, 'LatchLowerPlateProfile', x=-12)
    polygon(s, [(-half_w-8, HEIGHT-22), (-half_w-5.5, HEIGHT-22),
                (-half_w-5.5, HEIGHT-10), (-half_w-8, HEIGHT-10)])
    feature(latch, s, 24, 'LatchLowerPlate')
    hook_top = HEIGHT-20-0.05
    s = sketch(latch, 'SnapHookProfile', x=-12)
    polygon(s, [(-half_w-8, HEIGHT-22), (-half_w-3.4, HEIGHT-22),
                (-half_w-4.7, hook_top-0.4), (-half_w-4.7, hook_top),
                (-half_w-5.5, hook_top), (-half_w-5.5, HEIGHT-19),
                (-half_w-8, HEIGHT-19)])
    feature(latch, s, 24, 'SnapHook')
    s = sketch(latch, 'FingerLipProfile', x=-12)
    polygon(s, [(-half_w-10, HEIGHT-22), (-half_w-7, HEIGHT-22),
                (-half_w-7, HEIGHT-20), (-half_w-10, HEIGHT-20)])
    feature(latch, s, 24, 'FingerLip')

    # All trays use one local footprint; only their assembly placement differs.
    short = (LENGTH-2*WALL-4*TRAY_GAP)/3
    long = 2*short+TRAY_GAP
    tray_z = FLOOR + TRAY_GAP
    tray_top = tray_z + TRAY_HEIGHT
    tool_x = -LENGTH/2+WALL+TRAY_GAP+short/2
    cable_x = tool_x+short/2+TRAY_GAP+long/2
    slots = [App.Placement(V(tool_x, 0, 0), App.Rotation()),
             App.Placement(V(cable_x, -(short+TRAY_GAP)/2, 0), App.Rotation(V(0,0,1),90)),
             App.Placement(V(cable_x, (short+TRAY_GAP)/2, 0), App.Rotation(V(0,0,1),90))]
    trays = []
    for name, placement in zip(('ToolTray', 'CableTrayFront', 'CableTrayBack'), slots):
        w, h, x, y = short, long, 0, 0
        tray = doc.addObject('PartDesign::Body', name)
        tray.Label = name + f' — removable {w:.1f} x {h:.1f} mm'
        s = sketch(tray, name+'Outline', z=tray_z)
        rounded_rectangle(s, w, h, 5, x=x, y=y)
        feature(tray, s, TRAY_HEIGHT, name+'Blank')
        s = sketch(tray, name+'Interior', z=tray_top)
        rounded_rectangle(s, w-2*TRAY_WALL, h-2*TRAY_WALL, 2.6, x=x, y=y)
        feature(tray, s, TRAY_HEIGHT-TRAY_WALL, name+'Cavity', cut=True)
        dress_edges(tray, 'Chamfer', tray_z, BOTTOM_CHAMFER, name+'BottomChamfer')
        dress_edges(tray, 'Fillet', tray_top, RIM_FILLET, name+'RimFillet')
        # Inward pull ledge: underside grows 6 mm inward over 8 mm rise.
        # 36.9 degrees from vertical, with no horizontal unsupported underside.
        grip_depth, grip_width = 6.0, 24.0
        inner_y = y+h/2-TRAY_WALL
        s = sketch(tray, name+'PullHandleProfile', x=x-grip_width/2)
        polygon(s, [(inner_y+0.5, tray_top-11.2),
                    (inner_y, tray_top-11.2),
                    (inner_y-grip_depth, tray_top-3.2),
                    (inner_y-grip_depth, tray_top-1.2),
                    (inner_y+0.5, tray_top-1.2)])
        feature(tray, s, grip_width, name+'InwardPullHandle')
        dress_edges(tray, 'Fillet', tray_top-1.2, 0.5, name+'HandleEdgeFillet')
        if name == 'ToolTray':
            cradle_top = tray_z + TRAY_WALL + TOOL_THICKNESS + 1
            cradle_length = TOOL_LENGTH + 2*TOOL_CLEARANCE + 6
            # Seat the cradle at the front inner wall, not in the tray's center.
            tool_y = y-h/2+TRAY_WALL+cradle_length/2
            s = sketch(tray, 'ToolCradleFootprint', z=tray_z+TRAY_WALL)
            rectangle(s, w-2*TRAY_WALL, cradle_length, x=x, y=tool_y)
            feature(tray, s, TOOL_THICKNESS+1, 'ToolCradle')
            s = sketch(tray, 'ToolSlotProfile', z=cradle_top)
            rounded_rectangle(s, TOOL_WIDTH+2*TOOL_CLEARANCE,
                              TOOL_LENGTH+2*TOOL_CLEARANCE, 4, x=x, y=tool_y)
            feature(tray, s, TOOL_THICKNESS+1, 'ToolSlot', cut=True)
            s = sketch(tray, 'USBReliefProfile', z=cradle_top)
            rectangle(s, 9, 17, x=x-17.5, y=tool_y)
            feature(tray, s, TOOL_THICKNESS+1, 'USBRelief', cut=True)
            s = sketch(tray, 'ToolFingerProfile', z=cradle_top)
            circle(s, 17, x=x+17, y=tool_y)
            feature(tray, s, 7, 'ToolFingerRecess', cut=True)
        tray.Placement = placement
        trays.append(tray)

    clip_doc = App.newDocument('CableClip')
    clip_doc.Label = 'Cable clip — separate printable accessory'
    clip = clip_doc.addObject('PartDesign::Body', 'CableClip')
    clip.Label = f'07 Double cable clip — side entry, cable {CABLE_DIAMETER:g} mm'
    clip_x = clip_y = clip_z = 0
    bore = CABLE_DIAMETER+2*CABLE_CLEARANCE
    spacing = bore+3.8
    clip_width = spacing+bore+5.2
    clip_depth = bore+4.6
    s = sketch(clip, 'CableClipOutline', z=clip_z)
    rounded_rectangle(s, clip_width, clip_depth, 3.8, x=clip_x, y=clip_y)
    feature(clip, s, CABLE_CLIP_HEIGHT, 'CableClipBlank')
    s = sketch(clip, 'CableChannels', z=clip_z+CABLE_CLIP_HEIGHT)
    for dx in (-spacing/2, spacing/2):
        circle(s, bore, clip_x+dx, clip_y)
    feature(clip, s, CABLE_CLIP_HEIGHT, 'CableChannelBores', cut=True)
    s = sketch(clip, 'CableSideEntries', z=clip_z+CABLE_CLIP_HEIGHT)
    for dx in (-spacing/2, spacing/2):
        cx = clip_x+dx
        # Bell-mouth entries guide the jacket; no connector has to pass through.
        polygon(s, [(cx-CABLE_MOUTH/2, clip_y), (cx+CABLE_MOUTH/2, clip_y),
                    (cx+CABLE_MOUTH/2, clip_y+clip_depth/2-1.4),
                    (cx+CABLE_MOUTH/2+0.7, clip_y+clip_depth/2+0.2),
                    (cx-CABLE_MOUTH/2-0.7, clip_y+clip_depth/2+0.2),
                    (cx-CABLE_MOUTH/2, clip_y+clip_depth/2-1.4)])
    feature(clip, s, CABLE_CLIP_HEIGHT, 'CableEntrySlots', cut=True)
    parts = [base, lid, latch, *trays]
    print_parts = [*parts, clip]

    for s in sketches:
        s.Visibility = False
    doc.recompute()

    # Export separate parts in printing orientation; no pin models are needed.
    (OUTPUT / 'stl').mkdir(exist_ok=True)
    for owner in print_parts:
        rotation = (App.Rotation(V(1, 0, 0), 180) if owner == lid else
                    App.Rotation(V(0, 1, 0), -90) if owner == latch else App.Rotation())
        mesh = MeshPart.meshFromShape(Shape=owner.Tip.Shape, LinearDeflection=0.12,
                                     AngularDeflection=0.2, Relative=False)
        mesh.transform(App.Placement(V(0, 0, 0), rotation).toMatrix())
        bb = mesh.BoundBox
        mesh.translate(-bb.XMin, -bb.YMin, -bb.ZMin)
        mesh.write(str(OUTPUT / 'stl' / f'organizer_a1mini_{owner.Name.lower()}.stl'))
    clip_doc.recompute()
    clip_doc.saveAs(str(OUTPUT / 'cable_clipper.FCStd'))
    doc.saveAs(str(OUTPUT / 'organizer_a1mini.FCStd'))
    print('DONE:', OUTPUT / 'organizer_a1mini.FCStd')
    print('Print base, lid, snap latch and 3 bento trays separately. PLA: 5 walls, 0.2 mm, 25% infill.')
    print('Back hinge: insert a 1.75 mm filament pin, approximately 153 mm long.')
    print('Front latch: insert a separate 1.75 mm filament pin, approximately 34 mm long; retain its ends.')
    print('Print the latch on its flat side. Lift its lower finger lip to release the catch.')
    print('Test latch flex and pin retention in PLA before a full print; do not assume support-free slicing.')
    print(f'Cable clip: two {bore:g} mm channels, {CABLE_MOUTH:g} mm mouths; print flat without support.')
    print('Light-duty cable management only: do not force stiff cables into PLA; enlarge the mouth if needed.')


if __name__ == '__main__':
    build()
