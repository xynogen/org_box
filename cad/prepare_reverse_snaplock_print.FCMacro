"""Export only the top receiver; reuse the already printed latch for the fit test."""
from pathlib import Path
import math
import FreeCAD as App
import Mesh
import MeshPart

ROOT = Path(__file__).resolve().parents[1]


def main():
    source = App.openDocument(str(ROOT / 'reverse_snaplock_v3.FCStd'))
    plate = App.newDocument('ReverseSnapLockFitTest')
    try:
        for name, x, rotation in [
            ('TopCoupon', 72, -90),
        ]:
            shape = source.getObject(name).Shape
            if not shape.isValid() or len(shape.Solids) != 1:
                raise RuntimeError(f'{name}: invalid source solid')
            mesh = MeshPart.meshFromShape(Shape=shape, LinearDeflection=0.03,
                                          AngularDeflection=0.1, Relative=False)
            mesh.transform(App.Placement(App.Vector(), App.Rotation(App.Vector(1, 0, 0), rotation)).toMatrix())
            bb = mesh.BoundBox
            mesh.translate(x-bb.XMin, 60-bb.YMin, -bb.ZMin)
            if not mesh.isSolid() or mesh.BoundBox.ZMin < -1e-5:
                raise RuntimeError(f'{name}: invalid print mesh')
            obj = plate.addObject('Mesh::Feature', name)
            obj.Mesh = mesh
            print(name, 'print size:', bb.XLength, bb.YLength, bb.ZLength, 'mm')
            bed_area = sum(f.Area for f in mesh.Facets if max(abs(p[2]) for p in f.Points) < 1e-5)
            overhang_area = sum(f.Area for f in mesh.Facets
                                if f.Normal.z < -math.sqrt(.5)-1e-6
                                and max(p[2] for p in f.Points) > .21)
            if bed_area < 20:
                raise RuntimeError(f'{name}: insufficient flat bed contact')
            print(f'{name}: bed contact {bed_area:.2f} mm2; >45-degree underside {overhang_area:.2f} mm2')
        output = ROOT / 'reverse_snaplock_top_15_3_fit_test.3mf'
        Mesh.export(plate.Objects, str(output))
        print('EXPORTED:', output)
        print('Not print-certified: inspect overhangs and keep supports out of snap gaps and mating surfaces.')
    finally:
        App.closeDocument(plate.Name)
        App.closeDocument(source.Name)


if __name__ == '__main__':
    main()
